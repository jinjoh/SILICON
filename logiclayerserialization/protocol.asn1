--                                                                                 
-- This file is part of the IC reverse engineering tool degate.                    
--                                                                                 
-- Copyright 2008, 2009 by Martin Schobert                                         
--                                                                                 
-- Degate is free software: you can redistribute it and/or modify                  
-- it under the terms of the GNU General Public License as published by            
-- the Free Software Foundation, either version 3 of the License, or               
-- any later version.                                                              
--                                                                                 
-- Degate is distributed in the hope that it will be useful,                       
-- but WITHOUT ANY WARRANTY; without even the implied warranty of                  
-- MERCHANTABILITY or FITNESS FOR A PARTICULAR PURPOSE.  See the                   
-- GNU General Public License for more details.                                    
--                                                                                 
-- You should have received a copy of the GNU General Public License               
-- along with degate. If not, see <http://www.gnu.org/licenses/>.                  
                                                                                


ObjectSetModule DEFINITIONS ::=
BEGIN

ExclusionArea ::= SEQUENCE {
     	min-x INTEGER,
	min-y INTEGER,
     	max-x INTEGER,
	max-y INTEGER,
	id INTEGER,
	layer INTEGER,
	description VisibleString,
	col Color
}

Annotation ::= SEQUENCE {
     	min-x INTEGER,
	min-y INTEGER,
     	max-x INTEGER,
	max-y INTEGER,
	id INTEGER,
	layer INTEGER,
	description VisibleString,
	col Color
}

Color ::= SEQUENCE {
	red INTEGER (0 .. 255),
	green INTEGER (0 .. 255),
	blue INTEGER (0 .. 255),
	alpha INTEGER (0 .. 255)
}

LogicModelConnection ::= SEQUENCE {
	object-id INTEGER,
	sub-id INTEGER
}

Wire ::= SEQUENCE {
     	from-x INTEGER,
	from-y INTEGER,
	to-x INTEGER,
	to-y INTEGER,
	diameter INTEGER,
	id INTEGER,
	layer INTEGER,
	name VisibleString,
	col1 Color,
	col2 Color,
	connections SEQUENCE OF LogicModelConnection }

GatePort ::= SEQUENCE {
	port-id INTEGER,
	connections SEQUENCE OF LogicModelConnection }

TemplateOrientationType ::= ENUMERATED {
	undefined (0),
	normal(1),
	flipped-up-down(2),
	flipped-left-right(3),
	flipped-both(4) }
	
Gate ::= SEQUENCE {
     	min-x INTEGER,
	min-y INTEGER,
     	max-x INTEGER,
	max-y INTEGER,
	gate-id INTEGER,
	id INTEGER,
	layer INTEGER,
	name VisibleString,
	ports SEQUENCE OF GatePort,
	master-orientation TemplateOrientationType }

ViaDirection ::= ENUMERATED { up (0), down (1) }

Via ::= SEQUENCE {
     	x INTEGER,
	y INTEGER,
	diameter INTEGER,
	direction ViaDirection,
	id INTEGER,
	layer INTEGER,
	name VisibleString,
	col Color,
	connections SEQUENCE OF LogicModelConnection }

PortType ::= ENUMERATED { in(0), out(1) }

GateTemplatePort ::= SEQUENCE {
	id INTEGER,
	port-name VisibleString,
	port-type PortType,
	relative-x-coord INTEGER,
	relative-y-coord INTEGER,
	col Color,
	diameter INTEGER}

GateTemplate ::= SEQUENCE {
	gate-id INTEGER,
	master-image-min-x INTEGER,
	master-image-min-y INTEGER,
	master-image-max-x INTEGER,
	master-image-max-y INTEGER,
	short-name VisibleString,
	description VisibleString,
	fill-col Color,
	frame-col Color,
	ports SEQUENCE OF GateTemplatePort }

Object ::= CHOICE {	
	wire [1] Wire,
	via [2] Via,
	gate [3] Gate,
	gate-template [4] GateTemplate,
	exclusion-area [5] ExclusionArea,
	annotation [6] Annotation
}

FileContent ::= SEQUENCE OF Object

END
